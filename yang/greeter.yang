module greeter {
    yang-version 1.1;
    namespace "srlinux.dev/ndk/greeter";
    prefix "srl-labs-greeter";

    description
        "greeter YANG module";

    revision "2023-11-21" {
        description
            "initial release";
    }

    container greeter {
        leaf name {
            description
                "name of the person to greet";
            type string;
        }
        container currentstatus {
            description "The status";
            leaf greeting {
                description
                    "greeting the greeter will say";
                type string;
                config false;
            }
            config false;
        }
    }
}
